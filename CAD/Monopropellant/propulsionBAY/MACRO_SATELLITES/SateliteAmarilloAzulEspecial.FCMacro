# -*- coding:utf-8 -*-
import FreeCAD as App, FreeCADGui as Gui, Part, math

# =========================
# Documento
# =========================
doc_name = "CassiniUltra_HeavySatellite_RadiationShield"
if App.ActiveDocument is None or App.ActiveDocument.Label != doc_name:
    App.newDocument(doc_name)
doc = App.ActiveDocument

# =========================
# Parámetros
# =========================
P = {
    "tank_len":9800.0,"tank_d":5200.0,"hull_t":55.0,"hull_outer_d":6000.0,"liner_t":22.0,
    "tps_front_R":3600.0,"tps_front_t":160.0,"tps_offset":680.0,"shoulder_len":1300.0,
    "shade_len":1900.0,"shade_w":1500.0,"shade_t":110.0,"shade_r":2800.0,
    "strut_d":300.0,"strut_r":2150.0,
    "bus_len":3800.0,"bus_outer_d":5800.0,"bus_inner_d":5000.0,
    "hga_R":2400.0,"hga_t":26.0,"hga_offset":720.0,"hga_mast_len":1600.0,"hga_mast_d":240.0,
    "rtg_box_l":1500.0,"rtg_box_w":820.0,"rtg_box_t":360.0,"rtg_arm_len":1450.0,"rtg_arm_d":260.0,"rtg_arm_offset_z":1200.0,
    "chamber_len":3000.0,"chamber_d":2500.0,"throat_d":820.0,"exit_d":5200.0,
    "nozzle_len":4200.0,"nozzle_mid_d":3000.0,"nozzle_mid_x":1200.0,
    "gimbal_ring_ro":2500.0,"gimbal_ring_ri":2200.0,"gimbal_ring_t":120.0,
    "aft_shield_len":1800.0,"aft_shield_d1":5000.0,"aft_shield_d2":3200.0,
    "mast_len":2800.0,"mast_d":200.0,"mast_tip_R":360.0,"mast_tip_t":14.0,
    "solar_len":5200.0,"solar_w":1800.0,"solar_t":95.0,
    "solar2_len":3600.0,"solar2_w":1200.0,"solar2_t":80.0,
    "rad_len":2800.0,"rad_w":1100.0,"rad_t":52.0,"rad_z":1600.0,
    "tank_dome_R":2200.0,"tank_dome_t":32.0,
    "bulkhead_t":56.0,
    "frame_ring_d":3800.0,"frame_ring_t":110.0,"frame_strut_d":320.0,"frame_plinth_t":70.0,"frame_step":700.0,
    "engine_bay_len":2400.0,"pump_len":1400.0,"pump_d":1100.0,
    "line_LH2_d":360.0,"line_OX_d":400.0,"line_clearance":340.0,"line_bend_R":520.0,
    "rcs_thr_d":420.0,"rcs_thr_len":820.0,"rcs_ring_R":3400.0,"rcs_count":8,
    "aux_thr_d":1000.0,"aux_thr_len":1600.0,"aux_thr_ring_R":3600.0,"aux_thr_count":8,
    "rad_shield_inner_d":6400.0,"rad_shield_t":160.0,"rad_shield_gap":80.0,"rad_shield_len":6000.0,
    "whipple_t":45.0,"whipple_gap":220.0,
    "payload_bay_len":2400.0,"payload_bay_d":5200.0,"inst_bay_len":1800.0,"inst_bay_d":4200.0,
    "bat_box_l":1400.0,"bat_box_w":900.0,"bat_box_t":480.0,
    "sga_R":800.0,"sga_t":16.0,
    "mag_boom_len":4200.0,"mag_boom_d":160.0,"star_boom_len":3200.0,"star_boom_d":140.0,
    "fin_len":1400.0,"fin_w":760.0,"fin_t":110.0,
    "ion_thr_d":300.0,"ion_thr_len":900.0,"ion_ring_R":3000.0,"ion_count":12,
    "hall_thr_d":600.0,"hall_thr_len":1200.0,"hall_arm_len":1600.0,"hall_arm_d":180.0,
    "robot_link_d":180.0,"robot_link_len":1200.0,"robot_count":2,"end_eff_d":260.0,
    "parker_shield_R":2400.0,"parker_shield_t":160.0,
}

# =========================
# Utilidades geométricas
# =========================
X_AXIS, Y_AXIS, Z_AXIS = App.Vector(1,0,0), App.Vector(0,1,0), App.Vector(0,0,1)
rot_to_x = lambda: App.Rotation(Y_AXIS, 90)

def add_obj(s, n):
    o = doc.addObject("Part::Feature", n)
    o.Shape = s
    return o

def color(o, rgb):
    if hasattr(o, "ViewObject"): o.ViewObject.ShapeColor = rgb

def cyl_x(d, L, cx=0, cy=0, cz=0):
    s = Part.makeCylinder(d/2.0, L)
    s.Placement = App.Placement(App.Vector(cx - L/2.0, cy, cz), rot_to_x())
    return s

def cone_x(d1, d2, L, cx=0, cy=0, cz=0):
    s = Part.makeCone(d1/2.0, d2/2.0, L)
    s.Placement = App.Placement(App.Vector(cx - L/2.0, cy, cz), rot_to_x())
    return s

def circle_wire(d, cx, cy=0, cz=0):
    return Part.Wire([Part.Circle(App.Vector(cx, cy, cz), X_AXIS, d/2.0).toShape()])

def box_at(l, w, t, x, y, z, n, rgb=(0.5,0.5,0.5)):
    b = Part.makeBox(l, w, t)
    b.translate(App.Vector(x, y, z))
    o = add_obj(b, n)
    color(o, rgb)
    return o

def pipe_x(d, L, cx, cy, cz, n, rgb=(0.6,0.6,0.65)):
    p = cyl_x(d, L, cx, cy, cz)
    o = add_obj(p, n)
    color(o, rgb)
    return o

# =========================
# Construcción principal
# =========================
tank_cx = 0.0

# Tanque y casco
tank = add_obj(cyl_x(P["tank_d"], P["tank_len"], cx=tank_cx), "Tank"); color(tank, (0.20,0.60,1.00))
liner = add_obj(cyl_x(P["tank_d"] - 2*P["liner_t"], P["tank_len"] - 2*P["liner_t"], cx=tank_cx), "TankLiner"); color(liner, (0.15,0.45,0.85))
hull = add_obj(cyl_x(P["hull_outer_d"], P["tank_len"], cx=tank_cx).cut(tank.Shape), "HullOuter"); color(hull, (0.12,0.28,0.50))

# Bus
bus_shell = add_obj(cyl_x(P["bus_outer_d"], P["bus_len"], cx=tank_cx).cut(cyl_x(P["bus_inner_d"], P["bus_len"] - 2*P["hull_t"], cx=tank_cx)), "BusDeck")
color(bus_shell, (0.35,0.35,0.42))

# TPS frontal
R, tps_t = P["tps_front_R"], P["tps_front_t"]
cap_center_x = tank_cx + P["tank_len"]/2.0 + P["tps_offset"]
sphere_out, sphere_in = Part.makeSphere(R), Part.makeSphere(R - tps_t)
sphere_out.Placement = sphere_in.Placement = App.Placement(App.Vector(cap_center_x, 0, 0), App.Rotation())
tps_box = Part.makeBox(2*R, 4*R, 4*R, App.Vector(cap_center_x, -2*R, -2*R))
tps_front = add_obj(sphere_out.common(tps_box).cut(sphere_in.common(tps_box)), "TPS_Front")
color(tps_front, (0.08,0.08,0.08))

# Shoulder
shoulder_cx = cap_center_x - P["shoulder_len"]/2.0
shoulder = add_obj(cone_x(2*R, P["hull_outer_d"], P["shoulder_len"], cx=shoulder_cx), "TPS_Shoulder")
color(shoulder, (0.10,0.10,0.12))

# Sombras
def make_shade(v, n):
    s = Part.makeBox(P["shade_len"], P["shade_w"], P["shade_t"])
    s.translate(App.Vector(cap_center_x - P["shade_len"]/2.0, 0, 0))
    s.translate(v)
    o = add_obj(s, n)
    color(o, (0.25,0.25,0.25))
    return o

r, w = P["shade_r"], P["shade_w"]
make_shade(App.Vector(0, r - w/2.0, 0), "Shade_Yp")
make_shade(App.Vector(0, -r - w/2.0, 0), "Shade_Yn")
make_shade(App.Vector(0, 0, r - w/2.0), "Shade_Zp")
make_shade(App.Vector(0, 0, -r - w/2.0), "Shade_Zn")

# Puntales
def strut_at(y, z, L, n):
    cx = tank_cx + P["tank_len"]/2.0 + L/2.0
    s = cyl_x(P["strut_d"], L, cx=cx, cy=y, cz=z)
    o = add_obj(s, n)
    color(o, (0.45,0.45,0.45))
    return o

strut_len = P["tps_offset"] + P["shoulder_len"]
for i, (y,z) in enumerate([(P["strut_r"],0),(-P["strut_r"],0),(0,P["strut_r"]),(0,-P["strut_r"])]):
    strut_at(y,z,strut_len,f"Strut_{i}")

# Refrescar
Gui.activeDocument().activeView().viewAxonometric()
App.ActiveDocument.recompute()
print("✅ Modelo CassiniUltra_HeavySatellite_RadiationShield generado sin errores.")
