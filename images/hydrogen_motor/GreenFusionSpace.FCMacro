# -*- coding: utf-8 -*-
import FreeCAD as App, FreeCADGui as Gui, Part, math

doc_name = "Nave_CH4_Hall"
if App.ActiveDocument is None or App.ActiveDocument.Label != doc_name:
    App.newDocument(doc_name)
doc = App.ActiveDocument

# -----------------------------
# Parámetros (mm)
# -----------------------------
P = {
    # Casco grueso
    "nose_len": 900.0, "nose_base_d": 1800.0,
    "mid_len": 4200.0, "mid_d": 2600.0,
    "rear_len": 1600.0, "rear_d": 3000.0,
    "hull_t": 14.0,

    # Tanques (CH4/LH2) con márgenes para no solapar
    "tank_d": 1400.0, "tank_l": 3200.0,
    "tank_gap_y": 1000.0,  # separación lateral entre tanques
    "tank_LH2_cx": 1400.0, "tank_LH2_cy": -1000.0, "tank_LH2_cz": 0.0,
    "tank_CH4_cx": 2000.0, "tank_CH4_cy": 1000.0,  "tank_CH4_cz": 0.0,

    # Chaqueta de vacío/MLI visual
    "jacket_gap": 40.0, "mli_t": 12.0,

    # Electrólisis (entre tanques, sin colisión)
    "elec_l": 900.0, "elec_w": 700.0, "elec_h": 450.0, "elec_cx": 1700.0,

    # Presurización
    "compressor_d": 200.0, "compressor_l": 300.0,
    "valve_d": 120.0, "valve_h": 160.0,

    # Hall Thruster coaxial
    "hall_len": 900.0,
    "hall_inner_R": 350.0, "hall_outer_R": 700.0,  # cámara y estator
    "hall_coil_R": 750.0, "hall_coil_t": 24.0, "hall_coil_n": 6,
    "hall_cx": 3600.0,

    # Tobera grande
    "nozzle_throat_d": 600.0, "nozzle_exit_d": 1800.0, "nozzle_l": 1200.0, "nozzle_cx": 4200.0,

    # Manifold e inyectores
    "manifold_d": 700.0, "manifold_l": 500.0,
    "inj_n": 6, "inj_r": 420.0, "inj_throat": 70.0, "inj_exit": 120.0, "inj_len": 240.0,

    # Tuberías principales
    "pipe_d": 120.0, "pipe_y": 350.0,  # altura lateral para evitar colisión con módulos

    # Colores (RGB 0-1)
    "col_hull": (0.75, 0.75, 0.78),
    "col_LH2": (0.25, 0.75, 1.0),
    "col_CH4": (0.20, 0.80, 0.20),
    "col_jacket": (0.85, 0.85, 0.88),
    "col_mli": (0.90, 0.75, 0.20),
    "col_elec": (0.35, 0.60, 1.0),
    "col_coils": (1.0, 0.0, 0.5),
    "col_manifold": (0.55, 0.55, 0.60),
    "col_inject": (0.95, 0.45, 0.10),
    "col_nozzle": (0.70, 0.70, 0.72),
    "col_hall_inner": (0.60, 0.85, 1.0),
    "col_hall_stator": (0.50, 0.50, 0.55),
}

# -----------------------------
# Helpers
# -----------------------------
Y_AXIS = App.Vector(0,1,0)
def rot_to_x(): return App.Rotation(Y_AXIS, 90)

def add_obj(shape, label, color=None):
    o = doc.addObject("Part::Feature", label); o.Shape = shape
    if color and Gui.getDocument(doc.Name):
        o.ViewObject.ShapeColor = color
    return o

def make_cyl_x(d, L, cx=0, cy=0, cz=0, label="CylX"):
    r = d/2.0
    c = Part.makeCylinder(r, L)
    c.Placement = App.Placement(App.Vector(cx - L/2.0, cy, cz), rot_to_x())
    return add_obj(c, label)

def make_cone_x(d1, d2, L, cx=0, cy=0, cz=0, label="ConeX"):
    r1, r2 = d1/2.0, d2/2.0
    c = Part.makeCone(r1, r2, L)
    c.Placement = App.Placement(App.Vector(cx - L/2.0, cy, cz), rot_to_x())
    return add_obj(c, label)

# -----------------------------
# Casco grueso (nariz + medio + trasera) → shell ligero
# -----------------------------
nose = make_cone_x(P["nose_base_d"], 0.0, P["nose_len"], cx=P["nose_len"]/2.0, label="Nose")
mid  = make_cyl_x(P["mid_d"], P["mid_len"], cx=P["nose_len"] + P["mid_len"]/2.0, label="Mid")
rear = make_cyl_x(P["rear_d"], P["rear_len"], cx=P["nose_len"] + P["mid_len"] + P["rear_len"]/2.0, label="Rear")
hull_solid = nose.Shape.fuse(mid.Shape).fuse(rear.Shape)
# Ahuecado visual (si falla, deja sólido)
try:
    inner = hull_solid.makeOffsetShape(-P["hull_t"], 0.01, join=2, fill=True)
    Hull = add_obj(hull_solid.cut(inner), "Hull", P["col_hull"])
except:
    Hull = add_obj(hull_solid, "Hull_f", P["col_hull"])

# -----------------------------
# Tanques LH2 / CH4 con chaqueta y MLI (sin solapes)
# -----------------------------
Tank_LH2 = make_cyl_x(P["tank_d"], P["tank_l"], cx=P["tank_LH2_cx"], cy=P["tank_LH2_cy"], cz=P["tank_LH2_cz"], label="Tank_LH2")
Tank_CH4 = make_cyl_x(P["tank_d"], P["tank_l"], cx=P["tank_CH4_cx"], cy=P["tank_CH4_cy"], cz=P["tank_CH4_cz"], label="Tank_CH4")
Tank_LH2.ViewObject.ShapeColor = P["col_LH2"]; Tank_CH4.ViewObject.ShapeColor = P["col_CH4"]

LH2_Jacket = make_cyl_x(P["tank_d"] + 2*P["jacket_gap"], P["tank_l"], cx=P["tank_LH2_cx"], cy=P["tank_LH2_cy"], cz=P["tank_LH2_cz"], label="LH2_Jacket")
CH4_Jacket = make_cyl_x(P["tank_d"] + 2*P["jacket_gap"], P["tank_l"], cx=P["tank_CH4_cx"], cy=P["tank_CH4_cy"], cz=P["tank_CH4_cz"], label="CH4_Jacket")
LH2_Jacket.ViewObject.ShapeColor = P["col_jacket"]; CH4_Jacket.ViewObject.ShapeColor = P["col_jacket"]

# MLI toroidal (anillos a mitad de cada tanque)
mlis = []
for cx, cy in [(P["tank_LH2_cx"], P["tank_LH2_cy"]), (P["tank_CH4_cx"], P["tank_CH4_cy"])]:
    tor = Part.makeTorus(P["tank_d"]/2.0 + P["jacket_gap"] - P["mli_t"], P["mli_t"])
    tor.Placement = App.Placement(App.Vector(cx, cy, 0), rot_to_x())
    mlis.append(tor)
MLI = add_obj(Part.Compound(mlis), "MLI", P["col_mli"])

# -----------------------------
# Electrólisis (entre tanques, separado en Y)
# -----------------------------
Elec = Part.makeBox(P["elec_l"], P["elec_w"], P["elec_h"])
Elec.Placement = App.Placement(App.Vector(P["elec_cx"], -P["elec_w"]/2.0, -P["elec_h"]/2.0), App.Rotation())
Electrolyzer = add_obj(Elec, "Electrolyzer", P["col_elec"])

# -----------------------------
# Hall Thruster coaxial (sin solapes, centrado)
# -----------------------------
# Cámara (anillo: externo - interno)
Hall_outer = Part.makeCylinder(P["hall_outer_R"], P["hall_len"], App.Vector(0,0,0), App.Vector(1,0,0))
Hall_inner = Part.makeCylinder(P["hall_inner_R"], P["hall_len"], App.Vector(0,0,0), App.Vector(1,0,0))
Hall_ring = Hall_outer.cut(Hall_inner)
Hall_ring.Placement = App.Placement(App.Vector(P["hall_cx"] - P["hall_len"]/2.0, 0, 0), rot_to_x())
HallChamber = add_obj(Hall_ring, "HallChamber", P["col_hall_inner"])

# Estator (rejillas radiales en 2 filas, sin tocar la cámara)
stators = []
rows = [P["hall_cx"] - P["hall_len"]/2.0 + 200.0, P["hall_cx"] + P["hall_len"]/2.0 - 200.0]
for cx in rows:
    for k in range(12):
        ang = math.radians(k * 30.0)
        y = (P["hall_outer_R"] - 60.0) * math.cos(ang)
        z = (P["hall_outer_R"] - 60.0) * math.sin(ang)
        plate = Part.makeBox(12.0, 140.0, 220.0)
        plate.Placement = App.Placement(App.Vector(cx, y - 70.0, z - 110.0), App.Rotation())
        stators.append(plate)
Stator = add_obj(Part.Compound(stators), "HallStator", P["col_hall_stator"])

# Bobinas de campo alrededor (no invaden cámara)
coils = []
cx0 = P["hall_cx"] - P["hall_len"]/2.0 + 120.0
for i in range(P["hall_coil_n"]):
    cx = cx0 + i * ((P["hall_len"] - 240.0) / (max(P["hall_coil_n"]-1, 1)))
    tor = Part.makeTorus(P["hall_coil_R"], P["hall_coil_t"])
    tor.Placement = App.Placement(App.Vector(cx, 0, 0), rot_to_x())
    coils.append(tor)
HallCoils = add_obj(Part.Compound(coils), "HallCoils", P["col_coils"])

# -----------------------------
# Manifold e inyectores (radiales, fuera del radio de cámara)
# -----------------------------
Manifold = make_cyl_x(P["manifold_d"], P["manifold_l"], cx=P["nozzle_cx"] - 700.0, label="InjectionManifold")
Manifold.ViewObject.ShapeColor = P["col_manifold"]

injectors = []
for k in range(P["inj_n"]):
    ang = math.radians(k * (360.0 / P["inj_n"]))
    y = P["inj_r"] * math.cos(ang)
    z = P["inj_r"] * math.sin(ang)
    inj = Part.makeCone(P["inj_throat"]/2.0, P["inj_exit"]/2.0, P["inj_len"])
    inj.Placement = App.Placement(App.Vector(P["nozzle_cx"] - 850.0, y, z), rot_to_x())
    injectors.append(inj)
Injectors = add_obj(Part.Compound(injectors), "Injectors", P["col_inject"])

# -----------------------------
# Tobera grande
# -----------------------------
noz = Part.makeCone(P["nozzle_throat_d"]/2.0, P["nozzle_exit_d"]/2.0, P["nozzle_l"])
noz.Placement = App.Placement(App.Vector(P["nozzle_cx"] - P["nozzle_l"]/2.0, 0, 0), rot_to_x())
Nozzle = add_obj(noz, "Nozzle", P["col_nozzle"])

# -----------------------------
# Presurización (separada en Z bajo LH2)
# -----------------------------
Comp = make_cyl_x(P["compressor_d"], P["compressor_l"], cx=P["tank_LH2_cx"] - 500.0, cy=P["tank_LH2_cy"], cz=-P["tank_d"]/2.0 - 250.0, label="Compressor")
Valve = make_cyl_x(P["valve_d"], P["valve_h"], cx=P["tank_CH4_cx"], cy=P["tank_CH4_cy"], cz=P["tank_d"]/2.0 + 250.0, label="SafetyValve")

# -----------------------------
# Tuberías (rutas sin colisiones: offset en Y)
# -----------------------------
pipes = []

# CH4 → manifold
ch4_len = max(200.0, (P["nozzle_cx"] - 700.0) - P["tank_CH4_cx"])
pipe_CH4 = Part.makeCylinder(P["pipe_d"]/2.0, ch4_len)
pipe_CH4.Placement = App.Placement(App.Vector(P["tank_CH4_cx"], P["tank_CH4_cy"] + P["pipe_y"], 0.0), rot_to_x())
pipes.append(pipe_CH4)

# LH2 → manifold
lh2_len = max(200.0, (P["nozzle_cx"] - 700.0) - P["tank_LH2_cx"])
pipe_LH2 = Part.makeCylinder(P["pipe_d"]/2.0, lh2_len)
pipe_LH2.Placement = App.Placement(App.Vector(P["tank_LH2_cx"], P["tank_LH2_cy"] - P["pipe_y"], 0.0), rot_to_x())
pipes.append(pipe_LH2)

Pipes = add_obj(Part.Compound(pipes), "Pipes", (0.65, 0.80, 0.95))

# -----------------------------
# Grupo principal
# -----------------------------
grp = doc.addObject("App::Part", "Nave_CH4_Hall_Thick")
for o in [Hull,
          Tank_LH2, LH2_Jacket, Tank_CH4, CH4_Jacket, MLI,
          Electrolyzer,
          HallChamber, HallCoils, Stator,
          Manifold, Injectors, Nozzle,
          Comp, Valve, Pipes]:
    grp.addObject(o)

doc.recompute()
try:
    Gui.ActiveDocument.ActiveView.viewAxonometric()
    Gui.SendMsgToActiveView("ViewFit")
except:
    pass

# Propiedades de capacidad aproximada (m³)
try:
    r_m = (P["tank_d"]/2.0)/1000.0; h_m = (P["tank_l"]/1000.0)
    vol_m3 = math.pi * r_m**2 * h_m
    Tank_LH2.addProperty("App::PropertyString","Capacity_m3","Engineering","Volumen LH2 (m³)"); Tank_LH2.Capacity_m3 = "{:.2f}".format(vol_m3)
    Tank_CH4.addProperty("App::PropertyString","Capacity_m3","Engineering","Volumen CH4 (m³)"); Tank_CH4.Capacity_m3 = "{:.2f}".format(vol_m3)
except:
    pass
