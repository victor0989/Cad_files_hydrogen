# -*- coding:utf-8 -*-
import FreeCAD as App, FreeCADGui as Gui, Part, math

doc_name = "Green_Ammonia_Motor_Extended"
if App.ActiveDocument is None or App.ActiveDocument.Label != doc_name:
    App.newDocument(doc_name)
doc = App.ActiveDocument

# -------------------------
# Parámetros del conjunto extendido
# -------------------------
P = {
    # Tanque NH3
    "tank_len": 2200.0, "tank_d": 1300.0, "hull_t": 14.0,
    # Bridas y puertos
    "flange_d": 240.0, "flange_t": 20.0, "port_d": 140.0, "port_l": 160.0,
    # Presurización
    "press_sphere_d": 480.0, "press_line_d": 45.0,
    # Líneas (diámetros externos)
    "feed_line_d": 90.0, "purge_line_d": 55.0, "relief_line_d": 65.0,
    # Válvulas (cuerpo simplificado)
    "valve_body_d": 170.0, "valve_body_l": 240.0, "valve_handwheel_d": 130.0,
    # Cámara y reactor
    "chamber_len": 950.0, "chamber_d": 750.0,
    "reactor_len": 550.0, "reactor_d": 520.0,
    "injector_plate_t": 22.0, "injector_throat_d": 300.0,
    "injector_holes_n": 28, "injector_hole_d": 12.0, "injector_pitch": 180.0,
    # Camisa de refrigeración
    "jacket_gap": 14.0, "jacket_inlet_d": 55.0, "jacket_outlet_d": 55.0,
    # Tobera tipo campana (loft)
    "throat_d": 300.0, "exit_d": 950.0, "nozzle_len": 850.0,
    "nozzle_mid_d": 620.0, "nozzle_mid_x": 320.0,
    # Extensión de tobera (vacío)
    "nozzle_ext_len": 600.0, "nozzle_ext_factor": 1.3,
    # Estructura y gimbal
    "gimbal_ring_ro": 780.0, "gimbal_ring_ri": 720.0, "gimbal_ring_t": 22.0,
    "lug_w": 130.0, "lug_t": 32.0, "lug_h": 180.0, "lug_n": 4,
    "strut_d": 45.0, "strut_len": 650.0,
    # Sensores (bosses)
    "boss_d": 65.0, "boss_h": 40.0, "boss_n": 8,
    # Tabique interno del tanque
    "baffle_t": 7.0, "baffle_offset": 550.0,
    # Adaptador superior
    "adapter_len": 520.0, "adapter_extra": 350.0,
    # Colocación (eje X como largo)
    "assembly_offset_x": 0.0
}

# -------------------------
# Utilidades
# -------------------------
X_AXIS = App.Vector(1,0,0); Y_AXIS = App.Vector(0,1,0); Z_AXIS = App.Vector(0,0,1)
def rot_to_x(): return App.Rotation(Y_AXIS, 90)
def add_obj(shape, name):
    o = doc.addObject("Part::Feature", name); o.Shape = shape; return o
def color(o, rgb):
    try: o.ViewObject.ShapeColor = rgb
    except: pass

def cyl_x(d, L, cx=0, cy=0, cz=0):
    s = Part.makeCylinder(d/2.0, L)
    s.Placement = App.Placement(App.Vector(cx - L/2.0, cy, cz), rot_to_x())
    return s

def cone_x(d1, d2, L, cx=0, cy=0, cz=0):
    s = Part.makeCone(d1/2.0, d2/2.0, L)
    s.Placement = App.Placement(App.Vector(cx - L/2.0, cy, cz), rot_to_x())
    return s

def sphere(cx, cy, cz, d):
    return Part.makeSphere(d/2.0, App.Vector(cx, cy, cz))

def circle_wire(d, cx, cy=0, cz=0):
    circle = Part.Circle(App.Vector(cx, cy, cz), App.Vector(1,0,0), d/2.0)
    return circle.toShape()

# Hemisferio-shell estable
def make_hemisphere_shell(center_x, radius, thickness, side='L'):
    sph_out = Part.makeSphere(radius, App.Vector(center_x, 0, 0))
    sph_in  = Part.makeSphere(radius - thickness, App.Vector(center_x, 0, 0))
    L = 10.0 * radius; W = 10.0 * radius; H = 10.0 * radius
    if side.upper() == 'L':
        box = Part.makeBox(L, W, H, App.Vector(center_x - L, -W/2.0, -H/2.0))
    else:
        box = Part.makeBox(L, W, H, App.Vector(center_x, -W/2.0, -H/2.0))
    hemi_out = sph_out.common(box)
    hemi_in  = sph_in.common(box)
    return hemi_out.cut(hemi_in)

# -------------------------
# Tanque NH3
# -------------------------
R = P["tank_d"]/2.0; t = P["hull_t"]
tank_cx = P["assembly_offset_x"]
headL_center_x = tank_cx - P["tank_len"]/2.0
headR_center_x = tank_cx + P["tank_len"]/2.0

tank_wall = cyl_x(P["tank_d"], P["tank_len"], cx=tank_cx)
tank_inner = cyl_x(P["tank_d"]-2*t, P["tank_len"], cx=tank_cx)
tank_shell = tank_wall.cut(tank_inner)

headL_shell = make_hemisphere_shell(headL_center_x, R, t, side='L')
headR_shell = make_hemisphere_shell(headR_center_x, R, t, side='R')

tank_total = tank_shell.fuse(headL_shell).fuse(headR_shell)
tank_obj = add_obj(tank_total, "NH3_Tank"); color(tank_obj, (0.2,0.6,1.0))

# Tabique interno
baffle = cyl_x(P["tank_d"]-2*t, P["baffle_t"], cx=tank_cx-P["baffle_offset"])
baffle_obj = add_obj(baffle, "Baffle"); color(baffle_obj,(0.3,0.3,0.3))

# -------------------------
# Presurización
# -------------------------
press_cx = headL_center_x - 650.0
press = sphere(press_cx,0,0,P["press_sphere_d"])
press_obj = add_obj(press,"Pressurant_Sphere"); color(press_obj,(1.0,0.86,0.0))

press_line = cyl_x(P["press_line_d"], 650.0, cx=press_cx+325.0, cy=P["tank_d"]/2.0+70.0)
press_line_obj = add_obj(press_line,"Press_Line"); color(press_line_obj,(1.0,0.86,0.0))

# -------------------------
# Puertos y válvulas
# -------------------------
def side_port(name,y_offset,d_ext,L,cx):
    tube = cyl_x(d_ext,L,cx=cx,cy=y_offset)
    br = cyl_x(d_ext+40.0,20.0,cx=cx+L/2.0+10.0,cy=y_offset)
    return add_obj(tube.fuse(br),name)

port_cx = tank_cx
feed_port = side_port("Port_Feed",  P["tank_d"]/2.0-120.0, P["feed_line_d"], 300.0, port_cx)
purge_port= side_port("Port_Purge",-P["tank_d"]/2.0+160.0, P["purge_line_d"],280.0, port_cx-350.0)
relief_port=side_port("Port_Relief",P["tank_d"]/2.0-40.0,  P["relief_line_d"],260.0, port_cx+200.0)
color(feed_port,(0.0,0.7,0.4))
color(purge_port,(0.0,0.7,0.9))
color(relief_port,(0.9,0.3,0.0))

def valve_inline(name,line_cx,y,body_d,body_l):
    body=cyl_x(body_d,body_l,cx=line_cx,cy=y)
    wheel=Part.makeTorus(P["valve_handwheel_d"]/2.0,10.0)
    wheel.Placement=App.Placement(App.Vector(line_cx,y,0),rot_to_x())
    return add_obj(body.fuse(wheel),name)

val_feed=valve_inline("Valve_Feed", port_cx-250.0,P["tank_d"]/2.0-120.0,P["valve_body_d"],P["valve_body_l"])
val_purge=valve_inline("Valve_Purge",port_cx-200.0,-P["tank_d"]/2.0+160.0,P["valve_body_d"]*0.75,P["valve_body_l"]*0.8)
val_relief=valve_inline("Valve_Relief",port_cx+320.0,P["tank_d"]/2.0-40.0,P["valve_body_d"]*0.85,P["valve_body_l"]*0.9)

# -------------------------
# Cámara y reactor
# -------------------------
chamber_cx = port_cx+P["tank_len"]/2.0+320.0
chamber_outer=cyl_x(P["chamber_d"],P["chamber_len"],cx=chamber_cx)
chamber_inner=cyl_x(P["chamber_d"]-2*t,P["chamber_len"],cx=chamber_cx)
chamber_shell=chamber_outer.cut(chamber_inner)
chamber_obj=add_obj(chamber_shell,"Chamber"); color(chamber_obj,(0.8,0.7,0.6))

reactor_cx=chamber_cx-P["chamber_len"]/2.0+P["reactor_len"]/2.0+90.0
reactor=cyl_x(P["reactor_d"],P["reactor_len"],cx=reactor_cx)
reactor_obj=add_obj(reactor,"Catalyst_Reactor"); color(reactor_obj,(0.9,0.9,0.5))

# Inyector
injector_plate_cx=chamber_cx+P["chamber_len"]/2.0-P["injector_plate_t"]/2.0
injector_plate=cyl_x(P["injector_throat_d"],P["injector_plate_t"],cx=injector_plate_cx)
holes=[]
for i in range(P["injector_holes_n"]):
    ang=360.0*i/P["injector_holes_n"]
    y=(P["injector_pitch"]/2.0)*math.cos(math.radians(ang))
    z=(P["injector_pitch"]/2.0)*math.sin(math.radians(ang))
    h=cyl_x(P["injector_hole_d"],P["injector_plate_t"]+1.0,cx=injector_plate_cx,cy=y,cz=z)
    holes.append(h)
holeS=holes[0]
for h in holes[1:]: holeS=holeS.fuse(h)
injector_plate=injector_plate.cut(holeS)
injector_obj=add_obj(injector_plate,"Injector_Plate"); color(injector_obj,(0.6,0.6,0.9))

# Camisa refrigeración
jacket_outer=cyl_x(P["chamber_d"]+2*P["jacket_gap"],P["chamber_len"]*0.75,cx=chamber_cx-P["chamber_len"]*0.1)
jacket_inner=cyl_x(P["chamber_d"],P["chamber_len"]*0.75,cx=chamber_cx-P["chamber_len"]*0.1)
jacket_shell=jacket_outer.cut(jacket_inner)
jacket_obj=add_obj(jacket_shell,"Cooling_Jacket"); color(jacket_obj,(0.4,0.8,0.9))

# -------------------------
# Tobera extendida
# -------------------------
throat_cx=injector_plate_cx+P["injector_plate_t"]/2.0+30.0
exit_cx=throat_cx+P["nozzle_len"]

w_throat=circle_wire(P["throat_d"],throat_cx)
w_mid=circle_wire(P["nozzle_mid_d"],throat_cx+P["nozzle_mid_x"])
w_exit=circle_wire(P["exit_d"],exit_cx)
loft=Part.makeLoft([w_throat,w_mid,w_exit],True)
nozzle_obj=add_obj(loft,"Nozzle"); color(nozzle_obj,(0.7,0.7,0.7))

exit_cx2=exit_cx+P["nozzle_ext_len"]
w_exit2=circle_wire(P["exit_d"]*P["nozzle_ext_factor"],exit_cx2)
loft_ext=Part.makeLoft([w_exit,w_exit2],True)
nozzle_ext_obj=add_obj(loft_ext,"Nozzle_Extension"); color(nozzle_ext_obj,(0.6,0.6,0.6))

# -------------------------
# Struts de soporte
# -------------------------
for i in range(P["lug_n"]):
    ang=360.0*i/P["lug_n"]
    y=(P["tank_d"]/2.0+50.0)*math.cos(math.radians(ang))
    z=(P["tank_d"]/2.0+50.0)*math.sin(math.radians(ang))
    strut=cyl_x(P["strut_d"],P["strut_len"],cx=(tank_cx+P["tank_len"]/2.0+P["strut_len"]/2.0),cy=y,cz=z)
    strut_obj=add_obj(strut,f"Strut_{i+1}"); color(strut_obj,(0.6,0.6,0.6))

# -------------------------
# Adaptador superior
# -------------------------
adapter_top=cone_x(P["tank_d"]+P["adapter_extra"],P["tank_d"],P["adapter_len"],cx=tank_cx-P["tank_len"]/2.0-P["adapter_len"]/2.0)
adapter_obj=add_obj(adapter_top,"Adapter_Top"); color(adapter_obj,(0.7,0.7,0.7))

# -------------------------
# Sensores
# -------------------------
for i in range(P["boss_n"]):
    ang=360.0*i/P["boss_n"]
    y=(P["tank_d"]/2.0+P["boss_h"]/2.0)*math.cos(math.radians(ang))
    z=(P["tank_d"]/2.0+P["boss_h"]/2.0)*math.sin(math.radians(ang))
    boss=cyl_x(P["boss_d"],P["boss_h"],cx=tank_cx,cy=y,cz=z)
    boss_obj=add_obj(boss,f"SensorBoss_{i+1}"); color(boss_obj,(0.9,0.5,0.2))

# -------------------------
# Aro de cardán
# -------------------------
ring_cx=chamber_cx-P["chamber_len"]/2.0-70.0
ring_outer=Part.makeTorus(P["gimbal_ring_ro"],P["gimbal_ring_t"]/2.0)
ring_outer.Placement=App.Placement(App.Vector(ring_cx,0,0),rot_to_x())
ring_inner=Part.makeTorus(P["gimbal_ring_ri"],P["gimbal_ring_t"]/2.0)
ring_inner.Placement=App.Placement(App.Vector(ring_cx,0,0),rot_to_x())
gimbal_ring=ring_outer.cut(ring_inner)
gimbal_obj=add_obj(gimbal_ring,"Gimbal_Ring"); color(gimbal_obj,(0.5,0.5,0.5))

# -------------------------
# Agrupación
# -------------------------
grp=doc.addObject("App::Part","GreenAmmoniaMotor_Extended")
for o in doc.Objects:
    if o.Name not in [grp.Name]:
        grp.addObject(o)

doc.recompute()
try:
    Gui.ActiveDocument.ActiveView.viewAxonometric()
    Gui.SendMsgToActiveView("ViewFit")
except: pass
