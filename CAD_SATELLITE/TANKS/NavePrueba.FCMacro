# -*- coding: utf-8 -*-
import FreeCAD as App
import FreeCADGui as Gui
import Part
import math

DOC_NAME = "CassiniUltra_FullShielded"
doc = App.ActiveDocument
if not doc or doc.Label != DOC_NAME:
    doc = App.newDocument(DOC_NAME)
App.ActiveDocument = doc

P = {
    "tank_len": 9800.0, "tank_d": 5200.0, "hull_t": 55.0, "hull_outer_d": 6000.0, "liner_t": 22.0,
    "tps_front_R": 3600.0, "tps_front_t": 160.0, "tps_offset": 680.0, "shoulder_len": 1300.0,
    "bus_len": 3800.0, "bus_outer_d": 5800.0, "bus_inner_d": 5000.0, "hga_R": 2400.0, "hga_t": 26.0,
    "hga_offset": 720.0, "hga_mast_len": 1600.0, "hga_mast_d": 240.0, "chamber_len": 3000.0,
    "chamber_d": 2500.0, "throat_d": 820.0, "exit_d": 5200.0, "nozzle_len": 4200.0,
    "nozzle_mid_d": 3000.0, "nozzle_mid_x": 1200.0, "gimbal_ring_ro": 2500.0,
    "gimbal_ring_ri": 2200.0, "gimbal_ring_t": 120.0, "rcs_thr_d": 420.0, "rcs_thr_len": 820.0,
    "rcs_ring_R": 3400.0, "rcs_count": 8, "aux_thr_d": 1000.0, "aux_thr_len": 1600.0,
    "aux_thr_ring_R": 3600.0, "aux_thr_count": 8, "solar_len": 5200.0, "solar_w": 1800.0,
    "solar_t": 95.0, "rad_len": 2800.0, "rad_w": 1100.0, "rad_t": 52.0, "rad_z": 1600.0,
    "rad_shield_inner_d": 6400.0, "rad_shield_t": 160.0, "rad_shield_len": 6000.0,
    "whipple_t": 45.0, "whipple_gap": 220.0, "parker_shield_R": 2400.0, "parker_shield_t": 160.0
}

P.update({
    "cupola_R": 2000.0, "cupola_t": 35.0, "cupola_window_w": 420.0, "cupola_window_h": 680.0,
    "cupola_ring_t": 90.0, "cupola_phase_deg": 15.0, "cupola_windows_n": 8,
    "whipple_layers": 3, "whipple_segment_n": 12, "whipple_bumper_t": 8.0, "whipple_back_t": 28.0,
    "whipple_cover_len": 2800.0, "pipe_main_d": 160.0, "pipe_ox_d": 140.0, "pipe_fuel_d": 140.0,
    "pipe_wall_t": 3.0, "pipe_clearance": 180.0, "pipe_offset_phase": 20.0, "valve_len": 220.0,
    "valve_d": 220.0, "reg_len": 240.0, "manifold_d": 520.0, "manifold_len": 700.0,
    "turbopump_len": 820.0, "turbopump_d": 620.0, "volute_d": 720.0, "av_bay_len": 1800.0,
    "av_bay_w": 1400.0, "av_bay_h": 900.0, "rack_w": 480.0, "rack_h": 680.0, "rack_len": 600.0,
    "rack_count": 8, "battery_len": 600.0, "battery_w": 420.0, "battery_h": 380.0,
    "strut_d": 120.0, "strut_count": 12, "load_ring_t": 120.0, "sensor_mast_len": 1200.0,
    "sensor_mast_d": 180.0, "tracker_d": 280.0, "tracker_len": 240.0
})

STATE = {
    "flight_stowed": True, "deployed_solar": False, "thermal_test": False,
    "cupola_enabled": True, "whipple_enabled": True, "feedlines_enabled": True,
    "turbopump_enabled": True, "avionics_enabled": True, "sensors_enabled": True
}

DENS = {
    "CFRP": 1600, "Al": 2700, "Ti": 4500, "Cu": 8960, "Glass": 2500, "CeramicTPS": 3200,
    "CarbonShield": 2000, "Shield": 2000, "PEEK": 1320, "Kevlar": 1440, "Inconel": 8250
}

SUBSYS_MAT = {
    "Tank": "Al", "Liner": "Ti", "Hull": "CFRP", "TPS": "CeramicTPS", "Shield": "CarbonShield",
    "HGA": "Glass", "Solar": "CFRP", "Radiator": "Al", "RCS": "Ti", "Propulsion": "Ti",
    "Gimbal": "Ti", "Cupola": "CFRP", "CupolaWindow": "Glass", "WhippleBumper": "Kevlar",
    "WhippleBack": "Al", "Feedlines": "Ti", "Valves": "Ti", "Manifold": "Ti",
    "Turbopump": "Inconel", "AvionicsBay": "CFRP", "Rack": "Al", "Battery": "Al",
    "Strut": "Ti", "LoadRing": "Ti", "Sensors": "Al"
}

MARGIN_MODEL, MARGIN_INTEGRATION = 0.10, 0.05
mass_rollup = {}

X_AXIS = App.Vector(1, 0, 0)
Y_AXIS = App.Vector(0, 1, 0)
ROT_TO_X = App.Rotation(Y_AXIS, 90)


# ---------- Funciones utilitarias ----------
def place_x_aligned(s, L, cx=0, cy=0, cz=0):
    s.Placement = App.Placement(App.Vector(cx - L / 2, cy, cz), ROT_TO_X)


def add_obj(s, n, c=None):
    o = doc.addObject("Part::Feature", n)
    o.Shape = s
    if c:
        o.ViewObject.ShapeColor = c
    return o


def cyl_x(d, L, cx=0, cy=0, cz=0):
    s = Part.makeCylinder(d / 2, L)
    place_x_aligned(s, L, cx, cy, cz)
    return s


def cone_x(d1, d2, L, cx=0, cy=0, cz=0):
    s = Part.makeCone(d1 / 2, d2 / 2, L)
    place_x_aligned(s, L, cx, cy, cz)
    return s


def box_at(l, w, t, x, y, z):
    b = Part.makeBox(l, w, t)
    b.translate(App.Vector(x, y, z))
    return b


def add_group(n):
    return doc.addObject("App::DocumentObjectGroup", n)


def polar_positions(r, count, cx=0, z=0, phase=0):
    return [
        (cx,
         r * math.cos(math.radians(phase + 360 * i / count)),
         z + r * math.sin(math.radians(phase + 360 * i / count)))
        for i in range(count)
    ]


def mm3_to_m3(v):
    return v / 1e9


def mass(s, d):
    return mm3_to_m3(s.Volume) * d


def log_mass_subsys(subsys, s, mat):
    dens = DENS.get(mat, DENS.get("Al", 2700))
    m = mass(s, dens)
    m *= (1 + MARGIN_MODEL + MARGIN_INTEGRATION)
    mass_rollup[subsys] = mass_rollup.get(subsys, 0) + m
    return m


def fuse_safe(shapes):
    if not shapes:
        return None
    fused = shapes[0]
    for s in shapes[1:]:
        try:
            fused = fused.fuse(s)
        except Exception:
            pass
    return fused


def thicken_tube(d_outer, t_wall, L, cx=0, cy=0, cz=0):
    s_out = cyl_x(d_outer, L, cx, cy, cz)
    s_in = cyl_x(max(d_outer - 2 * t_wall, 1.0),
                 max(L - 2 * t_wall, 1.0),
                 cx, cy, cz)
    return s_out.cut(s_in)


def endcap_plate(d, t, cx, cy, cz):
    return cyl_x(d, t, cx=cx, cy=cy, cz=cz)


# ---------- Ensamblaje y subsistemas ----------
shapes = []

# Hull + TPS
hull = thicken_tube(P["hull_outer_d"], P["hull_t"], P["tank_len"])
tps_front = cyl_x(P["tps_front_R"] * 2, P["tps_front_t"], cx=P["tps_offset"])
shapes.append(hull.fuse(tps_front) if hull else tps_front)

# Bus
bus = cyl_x(P["bus_outer_d"], P["bus_len"])
shapes.append(bus)

# HGA
hga = cyl_x(P["hga_R"] * 2, P["hga_t"], cx=P["hga_offset"])
shapes.append(hga)

# Chamber & nozzle
chamber = cone_x(P["throat_d"], P["chamber_d"], P["chamber_len"])
nozzle = cone_x(P["chamber_d"], P["exit_d"], P["nozzle_len"], cx=P["nozzle_mid_x"])
shapes.append(chamber.fuse(nozzle))

# Gimbal ring
gimbal_ring = thicken_tube(P["gimbal_ring_ro"],
                           P["gimbal_ring_ro"] - P["gimbal_ring_ri"],
                           P["gimbal_ring_t"])
shapes.append(gimbal_ring)

# Solar panels
if STATE["deployed_solar"]:
    solar_panels = [
        box_at(P["solar_len"], P["solar_w"], P["solar_t"], x, 0, 0)
        for x in [-P["solar_len"] / 2, P["solar_len"] / 2]
    ]
    shapes += solar_panels

# Radiators
rads = [box_at(P["rad_len"], P["rad_w"], P["rad_t"], 0, 0, P["rad_z"])]
shapes += rads

# Whipple shield
if STATE["whipple_enabled"]:
    for i in range(P["whipple_layers"]):
        r_inner = P["rad_shield_inner_d"] / 2 + i * (P["whipple_t"] + P["whipple_gap"])
        bumper = thicken_tube(r_inner, P["whipple_bumper_t"], P["whipple_cover_len"])
        back = thicken_tube(r_inner + P["whipple_bumper_t"],
                            P["whipple_back_t"],
                            P["whipple_cover_len"])
        shapes.append(bumper.fuse(back))

# Cupola
if STATE["cupola_enabled"]:
    cup = thicken_tube(P["cupola_R"], P["cupola_t"], P["cupola_t"] * 2)
    shapes.append(cup)

# Feedlines / valves / turbopump
if STATE["feedlines_enabled"]:
    pipe_main = cyl_x(P["pipe_main_d"], P["turbopump_len"])
    shapes.append(pipe_main)

if STATE["turbopump_enabled"]:
    turbopump = thicken_tube(P["turbopump_d"], P["turbopump_d"] / 4, P["turbopump_len"])
    shapes.append(turbopump)

# Avionics racks
if STATE["avionics_enabled"]:
    racks = [box_at(P["rack_len"], P["rack_w"], P["rack_h"], x, 0, 0)
             for x in range(P["rack_count"])]
    shapes += racks

# Mass summary
for s, subsys, mat in zip(
    shapes,
    ["Hull", "Bus", "HGA", "Propulsion", "Gimbal", "Solar", "Radiator", "Shield",
     "Cupola", "Feedlines", "Turbopump", "AvionicsBay"],
    ["Hull", "Al", "Glass", "Ti", "Ti", "CFRP", "Al", "CarbonShield",
     "CFRP", "Ti", "Inconel", "CFRP"]
):
    log_mass_subsys(subsys, s, SUBSYS_MAT.get(mat, mat))

# Fusion final y agregado al documento
final_shape = fuse_safe(shapes)
add_obj(final_shape, "CassiniUltra_FullShielded_Assembly", (0.7, 0.7, 0.7))
doc.recompute()

# Mass rollup print
print("Mass rollup (kg):")
for k, v in mass_rollup.items():
    print(f"{k}: {v:.2f}")
