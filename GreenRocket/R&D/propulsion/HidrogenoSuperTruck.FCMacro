# -*- coding:utf-8 -*-
import FreeCAD as App,FreeCADGui as Gui,Part,math

doc_name="Quantum_Ion_Drive_Hybrid"
if App.ActiveDocument is None or App.ActiveDocument.Label!=doc_name:App.newDocument(doc_name)
doc=App.ActiveDocument

# ---------------- PARÁMETROS ----------------
P={
"fuel":"H2", 
"nose_len":700,"nose_base_d":1200,
"mid_len":2500,"mid_d":2500,
"rear_len":1800,"rear_d":2600,"hull_t":30,
"reactor_d":1800,"reactor_l":2000,"reactor_cx":3500,
"ring_h":60,"ring_ro":1400,"ring_ri":1300,"ring_n":24,"ring_pitch":150,
"coil_R":1400,"coil_rect_w":140,"coil_rect_h":140,"coil_n":16,"coil_span":2000,
"nozzle_throat_d":600,"nozzle_exit_d":2000,"nozzle_l":2000,"nozzle_cx":4300,
"sensor_enable":True,"sensor_d":70,"sensor_l":70,
"injector_n":20,"pipe_d":100,"pipe_l":1200,
"shield_enable":True,"shield_t":60,
"turbine_n":6,"turbine_d":250,"turbine_l":400,
"plasma_chamber_d":1200,"plasma_chamber_l":1600,
"cooling_pipe_d":80,"cooling_pipe_n":12
}

# Ajustes para Xe
if P["fuel"]=="Xe":P.update({"reactor_d":2200,"reactor_l":2400,"coil_n":20,"nozzle_throat_d":500,"nozzle_exit_d":1800,"pipe_d":120,"pipe_l":1400})

X_AXIS=App.Vector(1,0,0);Y_AXIS=App.Vector(0,1,0);Z_AXIS=App.Vector(0,0,1)
def rot_to_x():return App.Rotation(Y_AXIS,90)
def add_obj(s,l):o=doc.addObject("Part::Feature",l);o.Shape=s;return o
def make_cyl_x(d,L,cx=0,cy=0,cz=0,l="CylX"):c=Part.makeCylinder(d/2,L);c.Placement=App.Placement(App.Vector(cx-L/2,cy,cz),rot_to_x());return add_obj(c,l)
def make_cone_x(d1,d2,L,cx=0,cy=0,cz=0,l="ConeX"):c=Part.makeCone(d1/2,d2/2,L);c.Placement=App.Placement(App.Vector(cx-L/2,cy,cz),rot_to_x());return add_obj(c,l)
def make_hollow(o,t,l="Shell"): 
 try:i=o.makeOffsetShape(-t,0.01,join=2,fill=True);return add_obj(o.cut(i),l)
 except:return add_obj(o,l+"_f")

# ---------------- CONSTRUCCIÓN ----------------
# Carcasa externa
nose=make_cone_x(P["nose_base_d"],0,P["nose_len"],cx=P["nose_len"]/2,l="Nose")
mid=make_cyl_x(P["mid_d"],P["mid_len"],cx=P["nose_len"]+P["mid_len"]/2,l="Mid")
rear=make_cyl_x(P["rear_d"],P["rear_len"],cx=P["nose_len"]+P["mid_len"]+P["rear_len"]/2,l="Rear")
hull=make_hollow(nose.Shape.fuse(mid.Shape).fuse(rear.Shape),P["hull_t"],l="Hull")

# Reactor central y cámara de plasma
reactor_outer=make_cyl_x(P["reactor_d"],P["reactor_l"],cx=P["reactor_cx"],l="ReactorOuter")
plasma_chamber=make_cyl_x(P["plasma_chamber_d"],P["plasma_chamber_l"],cx=P["reactor_cx"],l="PlasmaChamber")
reactor=make_hollow(reactor_outer.Shape,P["hull_t"],"Reactor_Hollow")

# Anillos concéntricos tipo tokamak
rings=[]
x0=P["reactor_cx"]-P["reactor_l"]/2+P["ring_h"]/2
for i in range(P["ring_n"]):
 x=x0+i*P["ring_pitch"]
 r=Part.makeTorus((P["ring_ro"]+P["ring_ri"])/2,(P["ring_ro"]-P["ring_ri"])/2)
 r.Placement=App.Placement(App.Vector(x,0,0),rot_to_x())
 rings.append(r)
rS=rings[0]
for r in rings[1:]:rS=rS.fuse(r)
rings_obj=add_obj(rS,"Rings")

# Bobinas tokamak con deformación paramétrica
coils=[]
cx0=P["reactor_cx"]-P["coil_span"]/2
for i in range(P["coil_n"]):
 cx=cx0+i*(P["coil_span"]/(P["coil_n"]-1))
 radius=P["coil_R"]*(1+0.05*math.sin(i))
 coils.append(Part.makeTorus(radius,P["coil_rect_w"]/2).translate(App.Vector(cx,0,0)))
cS=coils[0]
for c in coils[1:]:cS=cS.fuse(c)
coils_obj=add_obj(cS,"Coils")

# Inyectores distribuidos
bars=[]
for i in range(P["injector_n"]):
 angle=i*(360/P["injector_n"])
 r=(P["ring_ro"]+P["ring_ri"])/2
 y=r*math.cos(math.radians(angle));z=r*math.sin(math.radians(angle))
 bar=Part.makeCylinder(35,P["reactor_l"]*0.9)
 bar.Placement=App.Placement(App.Vector(P["reactor_cx"]-P["reactor_l"]/2,y,z),rot_to_x())
 bars.append(bar)
bS=bars[0]
for b in bars[1:]:bS=bS.fuse(b)
bars_obj=add_obj(bS,"Injectors")

# Tuberías de combustible y refrigeración
pipes=[]
for i in range(P["injector_n"]):
 angle=i*(360/P["injector_n"])
 r=(P["ring_ro"]+P["ring_ri"])/2+70
 y=r*math.cos(math.radians(angle));z=r*math.sin(math.radians(angle))
 pipe=make_cyl_x(P["pipe_d"],P["pipe_l"],cx=P["reactor_cx"]-P["pipe_l"]/2,cy=y,cz=z,l=f"Pipe{i+1}")
 pipes.append(pipe)

# Turbinas internas de mezcla
turbines=[]
for i in range(P["turbine_n"]):
 angle=i*(360/P["turbine_n"])
 r=(P["reactor_d"]/2-50)
 y=r*math.cos(math.radians(angle));z=r*math.sin(math.radians(angle))
 turb=make_cyl_x(P["turbine_d"],P["turbine_l"],cx=P["reactor_cx"]+i*60,cy=y,cz=z,l=f"Turbine{i+1}")
 turbines.append(turb)

# Tobera
def make_nozzle():
 noz=Part.makeCone(P["nozzle_throat_d"]/2,P["nozzle_exit_d"]/2,P["nozzle_l"])
 noz.Placement=App.Placement(App.Vector(P["nozzle_cx"]-P["nozzle_l"]/2,0,0),rot_to_x())
 return add_obj(noz,"Nozzle")
noz_obj=make_nozzle()

# Sensores
sensor_objs=[]
if P["sensor_enable"]:
    for i in range(8):
        sensor=make_cyl_x(P["sensor_d"],P["sensor_l"],cx=P["reactor_cx"]+i*120,cy=0,cz=500-i*60,l=f"Sensor{i+1}")
        sensor_objs.append(sensor)

# Blindaje externo resistente
shield_obj=None
if P["shield_enable"]:
    shield_outer=make_cyl_x(P["reactor_d"]+2*P["shield_t"],P["reactor_l"]+2*P["shield_t"],cx=P["reactor_cx"],cy=0,cz=0,l="ShieldOuter")
    shield_obj=make_hollow(shield_outer.Shape,P["shield_t"],l="Shield_Hollow")

# Agrupación completa
parts=[hull, reactor, plasma_chamber, rings_obj, coils_obj, bars_obj, noz_obj]+pipes+turbines+sensor_objs
if shield_obj:
    parts.append(shield_obj)

grp=doc.addObject("App::Part","QuantumIonMotor_Hybrid")
for o in parts:
    grp.addObject(o)

# Recalcular y vista
doc.recompute()
try:
    Gui.ActiveDocument.ActiveView.viewAxonometric()
    Gui.SendMsgToActiveView("ViewFit")
except:
    pass
