# -*- coding: utf-8 -*-
# Macro FreeCAD: Direct Fusion Drive – Ensamblado coherente estilo Clipper
# Autor: Víctor + Copilot
# Unidades: mm, eje longitudinal = X

import FreeCAD as App, FreeCADGui as Gui, Part, math

doc_name = "DFD_Cohesion"
if App.ActiveDocument is None or App.ActiveDocument.Label != doc_name:
    App.newDocument(doc_name)
doc = App.ActiveDocument

# ========================
# Parámetros principales
# ========================
P = {
    "nose_len": 800.0, "nose_base_d": 600.0,
    "mid_len": 1400.0, "mid_d": 1200.0,
    "rear_len": 800.0, "rear_d": 1400.0,
    "hull_t": 15.0, "outer_t": 30.0,

    "reactor_d": 800.0, "reactor_l": 900.0,
    "nozzle_throat_d": 300.0, "nozzle_exit_d": 900.0, "nozzle_l": 700.0,

    "tank_D": 600.0, "tank_L": 1800.0, "tank_gap": 200.0,
    "panel_L": 8000.0, "panel_H": 2500.0, "panel_T": 40.0,
    "hga_D": 2500.0, "hga_mast_L": 800.0, "hga_mast_d": 180.0,
    "boom_L": 5000.0, "boom_D": 60.0
}

# ========================
# Utilidades
# ========================
X_AXIS=App.Vector(1,0,0); Y_AXIS=App.Vector(0,1,0); Z_AXIS=App.Vector(0,0,1)
def rot_to_x(): return App.Rotation(Y_AXIS,90)

def add_obj(s,l,c=None):
    o=doc.addObject("Part::Feature",l); o.Shape=s
    if c and Gui.getDocument(doc.Name): o.ViewObject.ShapeColor=c
    return o

def make_cyl_x(d,L,cx=0,cy=0,cz=0,l="CylX"):
    c=Part.makeCylinder(d/2.0,L)
    c.Placement=App.Placement(App.Vector(cx-L/2.0,cy,cz),rot_to_x())
    return add_obj(c,l)

def make_cone_x(d1,d2,L,cx=0,cy=0,cz=0,l="ConeX"):
    c=Part.makeCone(d1/2.0,d2/2.0,L)
    c.Placement=App.Placement(App.Vector(cx-L/2.0,cy,cz),rot_to_x())
    return add_obj(c,l)

def make_box(w,d,h,cx=0,cy=0,cz=0,l="Box"):
    b=Part.makeBox(w,d,h)
    b.Placement=App.Placement(App.Vector(cx-w/2.0,cy-d/2.0,cz-h/2.0),App.Rotation())
    return add_obj(b,l)

# ========================
# Fuselaje
# ========================
nose = make_cone_x(P["nose_base_d"],0,P["nose_len"],cx=P["nose_len"]/2,l="Nose")
mid  = make_cyl_x(P["mid_d"],P["mid_len"],cx=P["nose_len"]+P["mid_len"]/2,l="Mid")
rear = make_cyl_x(P["rear_d"],P["rear_len"],cx=P["nose_len"]+P["mid_len"]+P["rear_len"]/2,l="Rear")
bus  = add_obj(nose.Shape.fuse(mid.Shape).fuse(rear.Shape),"Bus")

bus_R = P["mid_d"]/2.0

# ========================
# Reactor + Tobera
# ========================
reactor = make_cyl_x(P["reactor_d"],P["reactor_l"],
                     cx=P["nose_len"]+P["mid_len"]+P["rear_len"]+P["reactor_l"]/2,
                     l="Reactor")
nozzle = make_cone_x(P["nozzle_throat_d"],P["nozzle_exit_d"],P["nozzle_l"],
                     cx=reactor.Shape.BoundBox.XMax+P["nozzle_l"]/2,
                     l="Nozzle")

# ========================
# Tanques laterales con soportes
# ========================
tank_cx = P["nose_len"]+P["mid_len"]/2
tank_offY = bus_R+P["tank_gap"]+P["tank_D"]/2
tankL = make_cyl_x(P["tank_D"],P["tank_L"],cx=tank_cx,cy=tank_offY,l="TankL")
tankR = make_cyl_x(P["tank_D"],P["tank_L"],cx=tank_cx,cy=-tank_offY,l="TankR")

# Brackets de unión
bracketL = make_box(200,80,200,cx=tank_cx,cy=(bus_R+P["tank_gap"]/2),cz=0,l="BracketL")
bracketR = make_box(200,80,200,cx=tank_cx,cy=-(bus_R+P["tank_gap"]/2),cz=0,l="BracketR")

# ========================
# Paneles solares con bisagras
# ========================
panel_hinge_y = bus_R+P["panel_T"]/2+100
panelL = make_box(P["panel_L"],P["panel_T"],P["panel_H"],
                  cx=tank_cx,cy=panel_hinge_y+P["panel_H"]/2,l="PanelL")
panelR = make_box(P["panel_L"],P["panel_T"],P["panel_H"],
                  cx=tank_cx,cy=-(panel_hinge_y+P["panel_H"]/2),l="PanelR")

hingeL = make_cyl_x(100,200,cx=tank_cx,cy=panel_hinge_y,l="HingeL")
hingeR = make_cyl_x(100,200,cx=tank_cx,cy=-panel_hinge_y,l="HingeR")

# ========================
# Antena HGA
# ========================
mast = make_cyl_x(P["hga_mast_d"],P["hga_mast_L"],
                  cx=tank_cx,cy=bus_R+400,cz=200,l="HGA_Mast")
dish = Part.makeSphere(P["hga_D"]/2.0)
cut = Part.makeBox(P["hga_D"],P["hga_D"],P["hga_D"]/2)
cut.Placement=App.Placement(App.Vector(-P["hga_D"]/2,-P["hga_D"]/2,0),App.Rotation())
dish = dish.cut(cut)
dish.Placement=App.Placement(App.Vector(tank_cx+P["hga_mast_L"],bus_R+400,200),App.Rotation())
hga = add_obj(dish,"HGA_Dish")

# ========================
# Boom magnetómetro
# ========================
boom = make_cyl_x(P["boom_D"],P["boom_L"],
                  cx=tank_cx,cy=-(bus_R+500),cz=200,l="Boom")

# ========================
# Agrupación
# ========================
grp = doc.addObject("App::Part","DFD_Ship_Cohesive")
for o in [bus,reactor,nozzle,tankL,tankR,bracketL,bracketR,
          panelL,panelR,hingeL,hingeR,mast,hga,boom]:
    grp.addObject(o)

doc.recompute()
try:
    Gui.ActiveDocument.ActiveView.viewAxonometric()
    Gui.SendMsgToActiveView("ViewFit")
except: pass

print("Nave DFD + Clipper ensamblada con coherencia en '{}'".format(doc.Label))
